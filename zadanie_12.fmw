FME workspace zadanie_12.fmw

Parameters:
- SourceDataset_SHAPEFILE = ""C:\Users\marce\Desktop\semestr 5\BDP\cw12\T2019_KAR_POI_TABLE.shp" "C:\Users\marce\Desktop\semestr 5\BDP\cw12\T2019_KAR_STREET_NODE.shp" "C:\Users\marce\Desktop\semestr 5\BDP\cw12\T2019_KAR_STREETS.shp""   # Source Esri Shapefile(s)
- SourceDataset_CSV2 = C:\Users\marce\Desktop\semestr 5\BDP\cw12\trasa.csv   # Source CSV (Comma Separated Value) File(s)

Readers:
- SHAPEFILE_1: SHAPEFILE from $(SourceDataset_SHAPEFILE)
- CSV2_1: CSV2 from $(SourceDataset_CSV2)

T2019_KAR_POI_TABLE (reader SHAPEFILE_1)
    attributes: POI_ID long, LINK_ID long, TYPE varchar(250), POI_NAME varchar(250), ST_NAME varchar(250), LAT number(31,15), LON number(31,15)
    -> Reprojector
T2019_KAR_STREET_NODE (reader SHAPEFILE_1)
    attributes: NODE_ID long, LINK_ID long, POINT_NUM long, Z_LEVEL long, INTERSECT varchar(1), LAT number(31,15), LON number(31,15)
    -> Reprojector
CSV (reader CSV2_1)
    attributes: x real32, y real32
    -> VertexCreator
VertexCreator
    MEASURE_TYPE_LOOKUP = CONTINUOUS
    MODE = REPLACE
    REMOVE_ATTRIBUTES = No
    XVAL = @Value(x)
    YVAL = @Value(y)
    MEASURE_TYPE = Continuous
    MODE_NAME = Replace with Point
    -> LineBuilder
LineBuilder
    ACCUM_INPUT_ATTRS_LOOKUP = One
    REMOVE_DUPLICATES_LOOKUP = NO
    ACCUM_INPUT_ATTRS = Use Attributes From One Feature
    REMOVE_DUPLICATES = No
    LINE -> Reprojector_2
Reprojector_2
    DEST = DHDN.Berlin/Cassini
    INTERPOLATION_TYPE = NearestNeighbor
    RASTER_CELL_SIZE = PreserveCells
    RASTER_TOLERANCE = 0.0
    SOURCE = LL-WGS84
    REPROJECTED -> ShortestPathFinder [FROM-TO]
    REPROJECTED -> ShortestPathFinder_2 [FROM-TO]
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> Reprojector
Reprojector
    DEST = DHDN.Berlin/Cassini
    INTERPOLATION_TYPE = NearestNeighbor
    RASTER_CELL_SIZE = PreserveCells
    RASTER_TOLERANCE = 0.0
    SOURCE = LL-WGS84
    REPROJECTED -> TestFilter
TestFilter
    DEFAULT_VALUE = <UNFILTERED>
    PASSED_TEST_GROUP_OUTPUT = FIRST
    TEST_LIST = "BOOL_OP,OR,COMPOSITE_TEST,""""""1"""""",TEST_CLAUSE,TEST @Value(fme_feature_type) = T2019_KAR_POI_TABLE",@Value(fme_feature_type) = T2019_KAR_POI_TABLE,"BOOL_OP,OR,COMPOSITE_TEST,""""""1"""""",TEST_CLAUSE,TEST @Value(fme_feature_type) = T2019_KAR_STREETS",@Value(fme_feature_type) = T2019_KAR_STREETS,"BOOL_OP,OR,COMPOSITE_TEST,""""""1"""""",TEST_CLAUSE,TEST @Value(fme_feature_type) = T2019_KAR_STREET_NODE",@Value(fme_feature_type) = T2019_KAR_STREET_NODE
    @Value(fme_feature_type) = T2019_KAR_POI_TABLE -> SpatialFilter [Candidate]
    @Value(fme_feature_type) = T2019_KAR_POI_TABLE -> SpatialFilter_4 [Candidate]
    @Value(fme_feature_type) = T2019_KAR_STREETS -> Tester
    @Value(fme_feature_type) = T2019_KAR_STREETS -> ShortestPathFinder [NETWORK]
    @Value(fme_feature_type) = T2019_KAR_STREET_NODE -> SpatialFilter_2 [Candidate]
    @Value(fme_feature_type) = T2019_KAR_STREET_NODE -> SpatialFilter_3 [Candidate]
Tester
    BOOL_OP = OR
    TEST_CLAUSE:
      TEST @Value(DIR_TRAVEL) = F
      TEST @Value(DIR_TRAVEL) = T
    TEST_MODE = TEST
    PASSED -> AttributeCreator
    FAILED -> AttributeCreator_2
AttributeCreator_2
    ATTR_TABLE:
      SET_TO ForwardCost (uint8) = 1
      SET_TO ReverseCost (uint8) = 1
    INPUT_PORT_CONNECTED = CONNECTED
    -> ShortestPathFinder_2 [NETWORK]
AttributeCreator
    ATTR_TABLE:
      SET_TO ForwardCost (varchar(200)) = FME_CONDITIONAL:DEFAULT_VALUE'999'BOOL_OP;OR;COMPOSITE_TEST;1;TEST @Value(DIR_TRAVEL) = F'1'FME_NUM_CONDITIONS2___
      SET_TO ReverseCost (varchar(200)) = FME_CONDITIONAL:DEFAULT_VALUE'999'BOOL_OP;OR;COMPOSITE_TEST;1;TEST @value(DIR_TRAVEL) = T'1'FME_NUM_CONDITIONS2___
    INPUT_PORT_CONNECTED = CONNECTED
    -> ShortestPathFinder_2 [NETWORK]
ShortestPathFinder_2
    ALLOW_UTURNS = No
    REORDER_MODE = NONE
    SNAP_POINTS = Yes
    SNAP_TOLERANCE = 200
    THREE_D = No
    WEIGHT_ATTR_1 = @Value(ForwardCost)
    WEIGHT_ATTR_2 = @Value(ReverseCost)
    WEIGHT_ATTR_CHOICE = BY_TWO_ATTRIBUTES
    PATH -> LengthCalculator
    PATH -> SpatialFilter_2 [Filter]
    PATH -> Bufferer
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> FeatureWriter_2 [Summary]
Bufferer
    ANGLE = 22.5
    CAP_STYLE_LOOKUP = CAP_ARC
    CORNER_STYLE_LOOKUP = JOIN_ARC
    MODE = AREA
    OFFSET = 5
    OFFSET_UNITS = NONE
    PRECISION = APPROX
    CAP_STYLE = Arc
    CORNER_STYLE = Arc
    BUFFERED -> SpatialFilter_4 [Filter]
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> FeatureWriter [Passed]
ShortestPathFinder
    ALLOW_UTURNS = Yes
    REORDER_MODE = NONE
    SNAP_POINTS = Yes
    SNAP_TOLERANCE = 200
    THREE_D = No
    WEIGHT_ATTR_CHOICE = BY_LENGTH
    PATH -> LengthCalculator
    PATH -> Bufferer_2
    PATH -> SpatialFilter_3 [Filter]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> FeatureWriter_2 [Summary]
FeatureWriter_2
    CONFIG_PARAMETERS = ESCAPE_COMMAS_IN_FTP_FORMAT_PARAMETERS,no
    DATASET = $(FME_MF_DIR_ENCODED)geodata_proejkt_12.gdb
    DATASET_ATTR = _dataset
    FEATURE_TYPE_LIST_ATTR = _feature_types
    FORMAT = GEODATABASE_FILE
    GEODATABASE_FILE_ALWAYS_CREATE_FEATURE_TYPES = NO
    GEODATABASE_FILE_ANNOTATION_UNITS = unknown_units
    GEODATABASE_FILE_CASE_CONTROL_ATTR_NAMES = none
    GEODATABASE_FILE_CASE_CONTROL_FT_NAMES = none
    GEODATABASE_FILE_COMPRESS_AT_END = no
    GEODATABASE_FILE_COORDINATE_SYSTEM_GRANULARITY = FEATURE_TYPE
    GEODATABASE_FILE_DEFAULT_Z_VALUE = 0
    GEODATABASE_FILE_DESTINATION_DATASETTYPE_VALIDATION = Yes
    GEODATABASE_FILE_DUMP_FAILED_FEATURES = no
    GEODATABASE_FILE_ENABLE_FAST_DELETES = yes
    GEODATABASE_FILE_ENABLE_LOAD_ONLY_MODE = no
    GEODATABASE_FILE_FEATURE_DATASET_HANDLING = WRITE
    GEODATABASE_FILE_GRID_1 = 0
    GEODATABASE_FILE_HAS_MEASURES = no
    GEODATABASE_FILE_HAS_Z_VALUES = auto_detect
    GEODATABASE_FILE_IGNORE_FAILED_FEATURE_ENTRY = no
    GEODATABASE_FILE_MAX_NUMBER_FAILED_FEATURES = -1
    GEODATABASE_FILE_OVERWRITE_GEODB = NO
    GEODATABASE_FILE_PRESERVE_GLOBALID = no
    GEODATABASE_FILE_RELATIONSHIP_WRITE_OVERRIDE = no
    GEODATABASE_FILE_REQUESTED_GEODATABASE_VERSION = CURRENT
    GEODATABASE_FILE_SIMPLIFY_GEOM = No
    GEODATABASE_FILE_SIMPLIFY_NETWORK_FEATURES = no
    GEODATABASE_FILE_TRANSACTION = 0
    GEODATABASE_FILE_TRANSACTION_INTERVAL = 1000
    GEODATABASE_FILE_TRANSACTION_TYPE = TRANSACTIONS
    GEODATABASE_FILE_VALIDATE_FEATURES = no
    GEODATABASE_FILE_XY_SCALE = 0
    GEODATABASE_FILE_X_ORIGIN = 0
    GEODATABASE_FILE_Y_ORIGIN = 0
    GEODATABASE_FILE_Z_ORIGIN = 0
    GEODATABASE_FILE_Z_SCALE = 0
    TOTAL_FEATURES_WRITTEN_ATTR = _total_features_written
Bufferer_2
    ANGLE = 22.5
    CAP_STYLE_LOOKUP = CAP_ARC
    CORNER_STYLE_LOOKUP = JOIN_ARC
    MODE = AREA
    OFFSET = 5
    OFFSET_UNITS = NONE
    PRECISION = APPROX
    CAP_STYLE = Arc
    CORNER_STYLE = Arc
    BUFFERED -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> FeatureWriter [Passed]
LengthCalculator
    DIM = 2
    LEN_ATTR = _length
    MULT = 1
    -> StatisticsCalculator
StatisticsCalculator
    ATTR_ACCUM_MODE = None
    CALCULATION_MODE = NUMERIC
    FEAT_STATS = _length,NUMERIC_MODE,,,,SUM,MEAN,,,,,,,,
    SUMMARY -> FeatureWriter [Passed]
FeatureWriter
    CONFIG_PARAMETERS = ESCAPE_COMMAS_IN_FTP_FORMAT_PARAMETERS,no
    DATASET = $(FME_MF_DIR_ENCODED)bez_kosztow_z_kosztami.json
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    GEOJSON_WRITE_FEATURE_IDS = Yes
    GEOJSON_WRITE_NESTED = YES
    TOTAL_FEATURES_WRITTEN_ATTR = _total_features_written
